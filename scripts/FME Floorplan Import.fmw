FME workspace FME Floorplan Import.fmw

Creator_2
    GEOMTYPE = Geometry Object
    NUM = 1
    CREATED -> FeatureReader [INITIATOR]
FeatureReader
    ACAD_ALLOW_DASH_CHAR_IN_ATTR_NAMES = yes
    ACAD_ALL_MERGED_FILTERS_NEED_NO_DEFS = Yes
    ACAD_APPLY_WORLD_FILE = yes
    ACAD_APPLY_WORLD_FILE_TO_ATTRS = YES
    ACAD_CONVERT_ZERO_LENGTH_ARCS_TO_POINTS = yes
    ACAD_EVALUATE_MLINE_GEOM = no
    ACAD_EXPLODE_MTEXT = yes
    ACAD_IGNORE_FROZEN_LAYERS = no
    ACAD_IGNORE_HIDDEN_LAYERS = yes
    ACAD_IGNORE_UCS = no
    ACAD_IGNORE_VIEWPORT_FROZEN_LAYERS = no
    ACAD_INTERPRET_EXTENDED_DATA = yes
    ACAD_LIST_ATTRIBUTE_ENTITY_DATA = yes
    ACAD_LIST_DYNAMIC_BLOCK_ATTRIBUTES = yes
    ACAD_LIST_EXTENDED_DATA = yes
    ACAD_METAFILE = acad
    ACAD_PREFERRED_COORD_SYS = ESRI
    ACAD_PRESERVE_CLIPPED_RASTERS = no
    ACAD_PRESERVE_COMPLEX_HATCHES = no
    ACAD_PRESERVE_INSERTS = no
    ACAD_QUERY_FEATURE_TYPES_FOR_MERGE_FILTERS = Yes
    ACAD_READ_AS_2_5D = no
    ACAD_READ_AS_GEOM_INSTANCES = no
    ACAD_READ_DYNAMIC_BLOCK_ATTRIBUTES = no
    ACAD_READ_GROUPS = no
    ACAD_READ_LAYER_DEFS = no
    ACAD_READ_MODEL_SPACE = yes
    ACAD_READ_PAPER_SPACE = NO
    ACAD_READ_PROXY_GRAPHICS = yes
    ACAD_READ_RASTERS = yes
    ACAD_READ_REGIONS_AS_AREAS = yes
    ACAD_READ_SYS_VARS = no
    ACAD_READ_USER_DICTIONARIES = no
    ACAD_READ_XREFS = no
    ACAD_RESOLVE_BLOCKS = yes
    ACAD_RESOLVE_DIMENSIONS = yes
    ACAD_RESOLVE_ENTITY_COLOR = yes
    ACAD_STORE_INSERT_POINT = no
    ACAD_STORE_LAYER_INFO = no
    ACAD_STORE_SPLINE_DEFS = yes
    ACAD_STRUCTURE_EXTENDED_DATA = no
    ACAD_USE_BLOCK_HEADER_LAYER = yes
    ACAD_USE_BLOCK_LAYER_INFO = no
    ACAD_USE_NEW_PAPER_SPACE_PARAMETERS = yes
    ACAD_USE_SEARCH_ENVELOPE = NO
    ACAD_VISIBLE_ATTRIBUTES_AS_TEXT = yes
    ACAD_XRECORD_READING = None
    ATTRIBUTES = 0,,A1------D-,,A1------H-,,A1------J-,,A1------N-,,A1------W-,,A1E0----E-,,A1E00---E-,,A1E00---T-,,A1E02---E-,,A1E2----E-,,A1E2----H-,,A1E4----E-,,A1E4----H-,,A1E46---E-,,A1E46---H-,,A1E5----E-,,A1E6----E-,,A1E6----H-,,A1E64---E-,,A1I4----E-,,A1I6----E-,,A1M11---E-,,A1M11---H-,,A1M16---E-,,A1M3----E-,,A1M61---E-,,A1M62---E-,,A1Z21---E-,,A1Z23---E-,,A1Z29---T-,,Defpoints,
    ATTR_ACCUM_MODE = Only Use Result
    CLIP_TO_ENVELOPE = NO
    COMBINE_GEOM = Use Result
    DATASET = D:\2011-DM-4. OG Bewirtschaftung DBB  2010-165820-2011DM.0.A04.6A1.dwg
    FORMAT = ACAD
    GEOMETRY_TYPES = 0,""",fme_arc,fme_area,fme_collection,fme_ellipse,fme_line,fme_point,fme_raster,fme_solid,fme_surface,fme_text""",A1------D-,""",fme_arc,fme_area,fme_collection,fme_ellipse,fme_line,fme_point,fme_raster,fme_solid,fme_surface,fme_text""",A1------H-,""",fme_arc,fme_area,fme_collection,fme_ellipse,fme_line,fme_point,fme_raster,fme_solid,fme_surface,fme_text""",A1------J-,""",fme_arc,fme_area,fme_collection,fme_ellipse,fme_line,fme_point,fme_raster,fme_solid,fme_surface,fme_text""",A1------N-,""",fme_arc,fme_area,fme_collection,fme_ellipse,fme_line,fme_point,fme_raster,fme_solid,fme_surface,fme_text""",A1------W-,""",fme_arc,fme_area,fme_collection,fme_ellipse,fme_line,fme_point,fme_raster,fme_solid,fme_surface,fme_text""",A1E0----E-,""",fme_arc,fme_area,fme_collection,fme_ellipse,fme_line,fme_point,fme_raster,fme_solid,fme_surface,fme_text""",A1E00---E-,""",fme_arc,fme_area,fme_collection,fme_ellipse,fme_line,fme_point,fme_raster,fme_solid,fme_surface,fme_text""",A1E00---T-,""",fme_arc,fme_area,fme_collection,fme_ellipse,fme_line,fme_point,fme_raster,fme_solid,fme_surface,fme_text""",A1E02---E-,""",fme_arc,fme_area,fme_collection,fme_ellipse,fme_line,fme_point,fme_raster,fme_solid,fme_surface,fme_text""",A1E2----E-,""",fme_arc,fme_area,fme_collection,fme_ellipse,fme_line,fme_point,fme_raster,fme_solid,fme_surface,fme_text""",A1E2----H-,""",fme_arc,fme_area,fme_collection,fme_ellipse,fme_line,fme_point,fme_raster,fme_solid,fme_surface,fme_text""",A1E4----E-,""",fme_arc,fme_area,fme_collection,fme_ellipse,fme_line,fme_point,fme_raster,fme_solid,fme_surface,fme_text""",A1E4----H-,""",fme_arc,fme_area,fme_collection,fme_ellipse,fme_line,fme_point,fme_raster,fme_solid,fme_surface,fme_text""",A1E46---E-,""",fme_arc,fme_area,fme_collection,fme_ellipse,fme_line,fme_point,fme_raster,fme_solid,fme_surface,fme_text""",A1E46---H-,""",fme_arc,fme_area,fme_collection,fme_ellipse,fme_line,fme_point,fme_raster,fme_solid,fme_surface,fme_text""",A1E5----E-,""",fme_arc,fme_area,fme_collection,fme_ellipse,fme_line,fme_point,fme_raster,fme_solid,fme_surface,fme_text""",A1E6----E-,""",fme_arc,fme_area,fme_collection,fme_ellipse,fme_line,fme_point,fme_raster,fme_solid,fme_surface,fme_text""",A1E6----H-,""",fme_arc,fme_area,fme_collection,fme_ellipse,fme_line,fme_point,fme_raster,fme_solid,fme_surface,fme_text""",A1E64---E-,""",fme_arc,fme_area,fme_collection,fme_ellipse,fme_line,fme_point,fme_raster,fme_solid,fme_surface,fme_text""",A1I4----E-,""",fme_arc,fme_area,fme_collection,fme_ellipse,fme_line,fme_point,fme_raster,fme_solid,fme_surface,fme_text""",A1I6----E-,""",fme_arc,fme_area,fme_collection,fme_ellipse,fme_line,fme_point,fme_raster,fme_solid,fme_surface,fme_text""",A1M11---E-,""",fme_arc,fme_area,fme_collection,fme_ellipse,fme_line,fme_point,fme_raster,fme_solid,fme_surface,fme_text""",A1M11---H-,""",fme_arc,fme_area,fme_collection,fme_ellipse,fme_line,fme_point,fme_raster,fme_solid,fme_surface,fme_text""",A1M16---E-,""",fme_arc,fme_area,fme_collection,fme_ellipse,fme_line,fme_point,fme_raster,fme_solid,fme_surface,fme_text""",A1M3----E-,""",fme_arc,fme_area,fme_collection,fme_ellipse,fme_line,fme_point,fme_raster,fme_solid,fme_surface,fme_text""",A1M61---E-,""",fme_arc,fme_area,fme_collection,fme_ellipse,fme_line,fme_point,fme_raster,fme_solid,fme_surface,fme_text""",A1M62---E-,""",fme_arc,fme_area,fme_collection,fme_ellipse,fme_line,fme_point,fme_raster,fme_solid,fme_surface,fme_text""",A1Z21---E-,""",fme_arc,fme_area,fme_collection,fme_ellipse,fme_line,fme_point,fme_raster,fme_solid,fme_surface,fme_text""",A1Z23---E-,""",fme_arc,fme_area,fme_collection,fme_ellipse,fme_line,fme_point,fme_raster,fme_solid,fme_surface,fme_text""",A1Z29---T-,""",fme_arc,fme_area,fme_collection,fme_ellipse,fme_line,fme_point,fme_raster,fme_solid,fme_surface,fme_text""",Defpoints,""",fme_arc,fme_area,fme_collection,fme_ellipse,fme_line,fme_point,fme_raster,fme_solid,fme_surface,fme_text"""
    INITIATOR_FIRST_OUTPUT = default
    INTERACT = NONE
    ORDER_RESULTS = No
    OUTPUT_ADD_SCHEMA_ATTRIBUTES = NO
    OUTPUT_FEATURES_DISPLAY = Schema and Data Features
    <OTHER> -> AttributeExposer
AttributeExposer
    ATTR_TABLE = autocad_layer,
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(autocad_layer) = A1Z21---E-",@Value(autocad_layer) = A1Z21---E-
    @Value(autocad_layer) = A1Z21---E- -> BoundingBoxAccumulator
    @Value(autocad_layer) = A1Z21---E- -> FeatureMerger_2 [REQUESTOR]
Rotator_2
    ANGLE = -170
    XORIG = 0
    YORIG = 0
    ROTATED -> CoordinateSystemSetter_2
CoordinateSystemSetter_2
    COORDSYS = CH1903Plus_1.LV95/01
    -> FeatureMerger [REQUESTOR]
Creator_4
    COORDSYS = CH1903Plus_1.LV95/01
    GEOM = <?xml version="1.0" encoding="US_ASCII" standalone="no" ?><geometry><point><coord x="2596118.43" y="1199458.2"/></point></geometry>
    GEOMTYPE = Geometry Object
    NUM = 1
    CREATED -> CoordinateExtractor
CoordinateExtractor
    IND = 0
    RECURSIVE = No
    X_ATTR = _target_x
    Y_ATTR = _target_y
    MODE = Specify Coordinate
    -> FeatureMerger [SUPPLIER]
FeatureMerger
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Offsetter
Offsetter
    MODE_LOOKUP = CARTESIAN
    XOFF = @Value(_target_x)
    YOFF = @Value(_target_y)
    ZOFF = 0
    MODE = Cartesian Coordinate
    OFFSET -> Reprojector
Reprojector
    DEST = LL-WGS84
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> FeatureWriter [Reprojected]
FeatureWriter
    DATASET = $(FME_MF_DIR_ENCODED)Fellerstrasse15.json
    DATASET_ATTR = _dataset
    FEATURE_TYPE_LIST_ATTR = _feature_types
    FORMAT = GEOJSON
    GEOJSON_COUNTER_CLOCKWISE_AREAS = Yes
    GEOJSON_DESTINATION_DATASETTYPE_VALIDATION = Yes
    GEOJSON_FILE_STRUCTURE = SINGLE_FEATURE_COLLECTION
    GEOJSON_INDENT_SIZE = 0
    GEOJSON_MAX_COORDINATE_PRECISION = 10
    GEOJSON_PRETTY_PRINT = YES
    GEOJSON_WGS84_REPROJECTION = Yes
    GEOJSON_WRITER_CHARSET = UTF-8
    GEOJSON_WRITE_BOM = No
    TOTAL_FEATURES_WRITTEN_ATTR = _total_features_written

Bookmark: Center to 0
BoundingBoxAccumulator
    ACCUM_ATTRS = One
    ACCUM_ATTRS_NAME = Use Attributes From One Feature
    BOUNDING_BOX -> CenterPointExtractor
CenterPointExtractor
    CENTX = _bound_x
    CENTY = _bound_y
    EXTRACTIONMODE = CENTER
    -> FeatureMerger_2 [SUPPLIER]
FeatureMerger_2
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Offsetter_2
Offsetter_2
    MODE_LOOKUP = CARTESIAN
    XOFF = 0@Value(_bound_x)*-1
    YOFF = 0@Value(_bound_y)*-1
    ZOFF = 0
    MODE = Cartesian Coordinate
    OFFSET -> Rotator_2
